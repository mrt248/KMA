FME workspace MPS_live.fmw

Parameters:
- DestDataset_POSTGIS = kma2015   # Destination PostGIS Dataset

Readers:
- MITAB_1: MITAB from ftp://rmk:pl!yYsk2a@ftp.maaamet.ee/MPS2RMK.zip in EPSG:3301

Writers:
- POSTGIS_1: POSTGIS to $(DestDataset_POSTGIS) in EPSG:3301

MPS_EESVOOL_kehtiv (reader MITAB_1)
    attributes: ID char(38), MS_KOOD char(13), EHITISE_KOOD char(3), NAHTUSE_LIIK char(13), EHITISE_NIMI char(35), EH_AASTA integer, EV_OSA char(1), VKOOD integer, VNIMI char(35), VIHM char(1), PIND decimal(6,1), PIKKUS decimal(6,2), KEHTIVUS char(1), KESKUS char(50), SISESTAJA char(50), SISEST_KP char(8), MUUTJA char(50), MUUT_KP char(8), TAPSUSKLASS decimal(6,2), MOODUSTUSVIIS char(8), KOORDINAATSYSTEEM char(8), MOODISTAJA char(50), MOODISTUSE_KP char(8), EKSPORT char(8)
    -> GeometryFilter
Note: Data Flow
GeometryFilter
    BREAK_AGG = No
    LINE -> TimeStamper
    ARC -> TimeStamper
TimeStamper
    TIME_ATTR = _timestamp
    FMT = FME Date (^Y^m^d)
    -> mets.MPS_line (writer POSTGIS_1)
mets.MPS_line (writer POSTGIS_1)
    attributes: gid serial,PRIKEY, keskus varchar(50), stamp_upd date, ms_kood varchar(13), ehitise_ko varchar(3), ehitise_ni varchar(50), ehitise_aa float8, ev_osa varchar(1), vkood float8, vnimi varchar(50), vihm int2, pindala float8, tapsusklas float8, moodustusv varchar(8), koordinaat varchar(8), moodistaja varchar(50), moodistuse date, id float8, ev_pikkus float8, sisestaja varchar(50), sisest_kp date, muutja varchar(50), muut_kp date, kehtivus int2, nahtuse_li varchar(20)
MPS_EHITIS_kehtiv (reader MITAB_1)
    attributes: ID char(38), MS_KOOD char(13), EHITISE_KOOD char(3), NAHTUSE_LIIK char(13), EHITISE_NIMI char(35), EH_AASTA integer, EV_OSA char(1), VKOOD integer, VNIMI char(35), VIHM char(1), PIND decimal(6,1), PIKKUS decimal(6,2), KEHTIVUS char(1), KESKUS char(50), SISESTAJA char(50), SISEST_KP char(8), MUUTJA char(50), MUUT_KP char(8), TAPSUSKLASS decimal(6,2), MOODUSTUSVIIS char(8), KOORDINAATSYSTEEM char(8), MOODISTAJA char(50), MOODISTUSE_KP char(8), EKSPORT char(8)
    -> GeometryFilter_2
GeometryFilter_2
    BREAK_AGG = No
    AREA -> TimeStamper_2
    ELLIPSE -> TimeStamper_2
TimeStamper_2
    TIME_ATTR = _timestamp
    FMT = FME Date (^Y^m^d)
    -> mets.MPS_polygon (writer POSTGIS_1)
mets.MPS_polygon (writer POSTGIS_1)
    attributes: gid serial,PRIKEY, keskus varchar(50), stamp_upd date, ms_kood varchar(13), ehitise_ko varchar(3), ehitise_ni varchar(50), ehitise_aa float8, ev_osa varchar(1), vkood float8, vnimi varchar(50), vihm int2, pindala float8, tapsusklas float8, moodustusv varchar(8), koordinaat varchar(8), moodistaja varchar(50), moodistuse date, id float8, ev_pikkus float8, sisestaja varchar(50), sisest_kp date, muutja varchar(50), muut_kp date, kehtivus int2, nahtuse_li varchar(20)
